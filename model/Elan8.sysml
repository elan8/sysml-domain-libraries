package Elan8 {
    public import Core;
    public import Documents;
    public import Electronics;
    public import Generation;
    public import Mechanical;
    public import PhysicalModeling;
    public import Procurement;
    public import Software;
    public import SystemsEngineering;
    public import Units;
}
