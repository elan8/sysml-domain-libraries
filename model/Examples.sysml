package Examples {
    package SystemsEngineering {
        public import RecursiveSystemExample;
    }
    package Electronics {
        public import MotorAndPowerModule;
        public import Pcba;
        public import RcCircuit;
        public import RlcCircuit;
        public import SensorSuite;
        public import StandardComponents;
    }
    package Mechanical {
        public import Composition;
        public import MassSpringSimulation;
        public import Pendulum;
    }
    package PhysicalModeling {
        public import MassSpringSimulation;
    }
    package Procurement {
        public import PartSourcingExample;
    }
    package Composition {
        public import BenchInstrumentExample;
    }
    package Software {
        public import GrpcServices;
        public import KafkaEvents;
        public import MessageBusExample;
        public import CSharpMapping;
        public import PythonMapping;
        public import RustMapping;
        public import LayeredApplication;
        public import WebShop;
        public import MotorController;
    }
}
