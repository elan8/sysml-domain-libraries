package SensorSuite {
    private import Elan8::Electronics::Core::*;
    private import Elan8::Electronics::Sensing::*;

    part def SensorSuite :> ElectronicsComponent {
        part imu : I2cInertialMeasurementUnit;
        part bumper : SwitchSensor;
        part lift : SwitchSensor;
        part wheelEncoder : PoweredQuadratureEncoder;
    }
}
