package Elan8 {
    package Mechanical {
        package Core {
            import Elan8::Core::*;
            private import ISQ::*;

            part def MechanicalComponent :> PhysicalComponent {
        
            }
        }
    }
}
